module sonic-interface {

	yang-version 1.1;

	namespace "http://github.com/sonic-net/sonic-interface";
	prefix intf;

	import sonic-types {
		prefix stypes;
	}

	import sonic-extension {
		prefix ext;
	}

	import sonic-port {
		prefix port;
		revision-date 2019-07-01;
	}

	import sonic-vrf {
		prefix vrf;
	}
	organization "SONiC";

	contact "SONiC";

	description "INTERFACE yang Module for SONiC OS";

	revision 2024-03-31 {
		description "Fixed linting errors";
		reference "RFC 8407";
	}

	revision 2021-03-30 {
		description "Modify the type of vrf name";
		reference "RFC 8407";
	}

	revision 2019-07-01 {
		description "First Revision";
		reference "RFC 8407";
	}

	container sonic-interface {
		description "INTERFACE top-level container";

		container INTERFACE {

			description "INTERFACE part of config_db.json";

			list INTERFACE_LIST {

				key "name";
				description "INTERFACE part of config_db.json with vrf";


				leaf name {
					type leafref {
						path /port:sonic-port/port:PORT/port:PORT_LIST/port:name;
					}
					description "INTERFACE name";
				}

				leaf vrf_name {
					type leafref {
						path "/vrf:sonic-vrf/vrf:VRF/vrf:VRF_LIST/vrf:name";
					}
					description "INTERFACE VRF name";
				}

				leaf nat_zone {
					type uint8 {
						range "0..3" {
							error-message "Invalid nat zone for the interface.";
							error-app-tag nat-zone-invalid;
						}
					}
                                        default "0";
					description "NAT Zone for the interface";
				}

				leaf mpls {
					type enumeration {
						enum enable {
							description "INTERFACE MPLS enable enum";
						}
						enum disable {
							description "INTERFACE MPLS disable enum";
						}
					}
					description "Enable/disable MPLS routing for the interface";
				}

				leaf ipv6_use_link_local_only {
					type stypes:mode-status;
					default disable;
					description "Enable/Disable IPv6 link local address on interface";
				}

                leaf loopback_action {
                    type stypes:loopback_action;
                    description "Packet action when a packet ingress and gets routed on the same IP interface";
                }
			}
			/* end of INTERFACE_LIST */

			list INTERFACE_IPPREFIX_LIST {

				key "name ip-prefix";
				description "INTERFACE part of config_db.json with ip-prefix";


				leaf name {
					/* This node must be present in INTERFACE_LIST */
					type leafref {
						path /port:sonic-port/port:PORT/port:PORT_LIST/port:name;
					}
					must "(current() = ../../INTERFACE_LIST[name=current()]/name)"
					{
						error-message "Must condition not satisfied, Try adding PORT: {}, Example: 'Ethernet0': {}";
					}

					description "INTERFACE Port List name";
				}

				leaf ip-prefix {
					type union {
						type stypes:sonic-ip4-prefix;
						type stypes:sonic-ip6-prefix;
					}
					description "INTERFACE Port List ip-prefix";
				}

				leaf scope {
					type enumeration {
						enum global {
							description "INTERFACE_IPPREFIX_LIST scope enum - global";
						}
						enum local {
							description "INTERFACE_IPPREFIX_LIST scope enum - local";
						}
					}
					description "INTERFACE_IPPREFIX_LIST scope";
				}

				leaf family {

					/* family leaf needed for backward compatibility
					   Both ip4 and ip6 address are string in IETF RFC 6021,
					   so must statement can check based on : or ., family
					   should be IPv4 or IPv6 according.
					 */

					type stypes:ip-family;
					must "(contains(../ip-prefix, ':') and current()='IPv6') or
						(contains(../ip-prefix, '.') and current()='IPv4')";
					description "INTERFACE_IPPREFIX_LIST address family";
				}
			}
			/* end of INTERFACE_IPPREFIX_LIST */

		}
		/* end of INTERFACE container */
	}
}
